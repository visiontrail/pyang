module certus-5gnr-types-for-du {
    namespace "http://certusnet.com/5gnr/certus-5gnr-types-for-du";
    prefix cgtfd;

    import ietf-inet-types { prefix inet; }
    
    organization "CertusNet";
    description "This module defines types used by 5gnr du.";
    
    revision 2019-07-08 {
        description  "Initial revision.";
    }
    
    typedef ip-version-e {
        type enumeration {
            enum IPV4;
            enum IPV6;
        }
    }
    typedef ns-agent-type-e {
        type enumeration {
            enum NS-DISABLED;
            enum NS-OAM-BASED;
            enum NS-SLICEMGR-BASED;
        }
    }
    typedef du-module-id-e {
        type enumeration {
            enum DU-NS-AGENT;
            enum DU-OAM-AGENT;
            enum DU-MGR;
            enum DU-RRM;
            enum DU-APP-UE;
            enum DU-F1AP;
            enum DU-SCTP;
            enum DU-EGTPU;
            enum DU-UDP;
            enum DU-NRUP;
            enum DU-RRC-CODEC;
            enum DU-COMMON-CODEC;
            enum DU-COMMON;
            enum DU-FAST-PKT;
        }
    }
    typedef ngp-module-id-e {
        type enumeration {
            enum NGP { description 0xFFFF0000; }
            enum NGP-MEM { description 0x1000; }
            enum NGP-BUF { description 0x1001; }
            enum NGP-STATS { description 0x1002; }
            enum NGP-TIMER { description 0x1003; }
            enum NGP-STHREAD { description 0x1004; }
            enum NGP-CTHREAD { description 0x1005; }
            enum NGP-SYS { description 0x1006; }
            enum NGP-EXCP { description 0x1007; }
            enum NGP-COMM { description 0x1008; }
            enum NGP-SCTP { description 0x1009; }
            enum NGP-UDP { description 0x100A; }
            enum NGP-TCP { description 0x100B; }
            enum NGP-MSGQ { description 0x100C; }
            enum NGP-PRIOQ { description 0x100D; }
            enum NGP-WORKQ { description 0x100E; }
            enum NGP-PERF { description 0x100F; }
            enum NGP-HTTP2 { description 0x1010; }
            enum NGP-THR_POOL { description 0x1011; }
        }
    }
    typedef log-lvl-e {
        type enumeration {
            enum LL-OFF;
            enum LL-FATAL;
            enum LL-ERROR;
            enum LL-WARN;
            enum LL-INFO;
            enum LL-TRACE;
        }
    }
    
    grouping ip-addr {
        leaf ip-version { type ip-version-e; }
        leaf ipv4-addr {
            if-feature optional;
            type inet:ipv4-address;
        }
        leaf ipv6-addr {
            if-feature optional;
            type inet:ipv6-address;
        }
    }
}
