submodule certus-5gnr-du-du-ns {
    belongs-to certus-5gnr-du-du {
        prefix cgdu;
    }

    import certus-5gnr-du-du-types {
        prefix cgddts;
        revision-date 2019-07-08;
    }

    organization "CertusNet";
    description "This module defines du network slice configuration.";

    revision 2019-07-08 {
        description  "Initial revision.";
    }


    grouping nsi {
        leaf nsi-id { type uint8; }
        leaf-list cores {
            type uint16;
            max-elements 32;
        }
    }
    
    
    grouping du-ns {
        leaf agent-type { type cgddts:ns-agent-type-e; }
        container local-sm {
            uses cgddts:ip-addr-port;
        }
        container remote-sm {
            uses cgddts:ip-addr-port;
        }
        list nsis {
            key nsi-id;
            uses nsi;
        }
        description "Network Slice";
    }
}
