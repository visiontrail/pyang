submodule certus-5gnr-du-du-base {
    belongs-to certus-5gnr-du-du {
        prefix cgdu;
    }
    
    import certus-5gnr-du-du-types {
        prefix cgddts;
        revision-date 2019-07-08;
    }
    
    organization "CertusNet";
    description "This module defines du base configuration.";
    
    revision 2019-07-08 {
        description "Initial revision.";
    }


    grouping du-module-log {
        leaf module-id { type cgddts:du-module-id-e; }
        leaf log-lvl { type cgddts:log-lvl-e; }
    }
    grouping ngp-module-log {
        leaf module-id { type cgddts:ngp-module-id-e; }
        leaf log-lvl { type cgddts:log-lvl-e; }
    }
    grouping rlog {
        leaf rlog-path { type string; }
        leaf rlog-file-name { type string; }
        leaf init-log { type uint8; }
        leaf module-mask { type uint32; }
        leaf num-of-rlog-files { type uint8; }
        leaf rlog-file-size-lmt { type uint32; }
        leaf rlog-level { type cgddts:rlog-lvl-e; }
    }


    grouping sctp {
        container dst {
            uses cgddts:ip-addr-port;
        }
        container src {
            uses cgddts:ip-addr-port;
        }
        container cfg-params {
            leaf num-outbound-streams { type uint16; }
            leaf max-inbound-streams { type uint16; }
            leaf max-init-attempts { type uint16; }
            leaf hb-interval { type uint16; }
            leaf max-path-retx { type uint16; }
        }
    }
    grouping drx {
        leaf drx-on-duration-tmr {
            if-feature optional;
            type uint32;
        }
        leaf inactivity-tmr { type uint32; }
        leaf drx-rtt-tmr-ul { type uint8; }
        leaf drx-rtt-tmr-dl { type uint8; }
        leaf retx-tmr-ul { type uint32; }
        leaf retx-tmr-dl { type uint32; }
        leaf long-cycle { type uint32; }
        leaf drx-cycle-start-offset { type uint32; }
        container short-cycle {
            if-feature optional;
            leaf short-cycle-tm { type uint32; }
            leaf short-cycle-tmr { type uint32; }
        }
        leaf drx-slot-offset { type uint32; }
    }
    grouping log {
        leaf file-name { type string; }
        list du-modules {
            key module-id;
            uses du-module-log;
        }
        list ngp-modules {
            key module-id;
            uses ngp-module-log;
        }
        container rlog {
            uses rlog;
        }
    }
    
    grouping du-base {
        leaf gnb-du-id { type uint64{ range "0..68719476735"; }}
        leaf gnb-du-name {
            if-feature optional;
            type string;
        }
        leaf max-cell-supported { type uint8; }
        container ue {
            leaf max-num-ues { type uint16; }
            leaf rnti-start { type uint16; }
            leaf max-num-rnti { type uint16; }
        }
        container sctp {
            uses sctp;
        }
        container egtpu {
            uses cgddts:ip-addr;
            leaf teid-min { type uint32; }
            leaf teid-max { type uint32; }
        }
        container f1u-flow-ctrl {
            leaf max-rlc-sdu-q-size { type uint16; }
            leaf rlc-sdu-q-lwr-thr { type uint16; }
            leaf rlc-sdu-q-upr-thr { type uint16; }
            leaf nrup-flw-ctrl-tmr { type uint16; }
            leaf ingress-pkt-read-per-tti { type uint8; }
        }
        container drx {
            if-feature optional;
            uses drx;
        }
        container log {
            uses log;
        }
    }
}
