submodule certus-5gnr-du-cell-l1 {
    belongs-to certus-5gnr-du-cells {
        prefix cgdcs;
    }

    import certus-5gnr-du-cell-types {
        prefix cgdcts;
        revision-date 2019-06-20;
    }

    organization "CertusNet";
    description "This module defines du cell L1 configuration.";
    
    revision 2019-06-20 {
        description  "Initial revision.";
    }
    
    grouping plmn-id-info {
        list plmn-ids {
            key "mcc mnc";
            uses cgdcts:plmn-id;
            min-elements 0;
            max-elements 6;
        }
        leaf nr-cell-id {
            type cgdcts:nr-cell-id-t;
        }
        leaf tac {
            type uint32;
            description "Tracking Area Code";
        }
        leaf ranac {
            type uint8 { range "0..255"; }
            description "RAN Area Code";
        }
        leaf cell-rsrvd-for-operator-use {
            type empty;
            description "Cell Reserved For Operator Use";
        }
    }
    
    
    grouping cell-sel-info {
        leaf q-rx-lvl-min {
            type cgdcts:q-rx-lvl-min-t;
            description "Minimum Received RSRP Level";
        }
        leaf q-rx-lvl-min-sul {
            type cgdcts:q-rx-lvl-min-t;
            description "Minimum Received RSRP Level Of SUL";
        }
        leaf q-qual-min {
            type cgdcts:q-qual-min-t;
            description "Minimum Received RSRQ Level";
        }
    }
    grouping cell-access-info {
        list plmn-id-infos {
            key nr-cell-id;
            uses plmn-id-info;
            
            min-elements 0;
            max-elements 6;
        }
    }
    grouping ue-timers {
        leaf t300 { type cgdcts:t300-e; }
        leaf t301 { type cgdcts:t301-e; }
        leaf t310 { type cgdcts:t310-e; }
        leaf n310 { type cgdcts:n310-e; }
        leaf t311 { type cgdcts:t311-e; }
        leaf n311 { type cgdcts:n311-e; }
        leaf t319 { type cgdcts:t319-e; }
    }
    

    grouping prach {
        leaf root-seq-idx {
            type uint16 { range "0..837"; }
        }
        leaf cfg-idx { type uint8; }
        leaf zero-correlation-zone-cfg {
            type uint8 { range "0..15"; }
        }
        leaf freq-offset {
            type uint8 { range "0..94"; }
        }
        leaf scs { type cgdcts:scs-e; }
        leaf restricted-set {
            if-feature optional;
            type cgdcts:restricted-set-cfg-e;
        }
        leaf freq-start {
            type uint16 { range "0..274"; }
         }
        leaf fdm { type cgdcts:msg1-fdm-e; }
        leaf ssb-per-rach-occ {
            type cgdcts:ssb-per-rach-occ-e;
            description "SSBs Number Per RACH Occasion";
        }
    }
    grouping mib {
        leaf scs-cmn {
            type cgdcts:scs-cmn-e;
            description "Subcarrier Spacing Common";
        }
        leaf ssb-sc-offset {
            type cgdcts:ssb-sc-offset-t;
            description "SSB Subcarrier Offset";
        }
        leaf cell-barred {
            type cgdcts:cell-barred-e;
        }
        leaf intra-freq-resel {
            type cgdcts:intra-freq-resel-e;
            description "Intra Frequency Reselection";
        }
        container pdcch-cfg-sib1 {
            leaf coreset-zero {
                type cgdcts:coreset-zero-t;
                description "Control Resource Set With ID #0";
            }
            leaf ss-zero {
                type cgdcts:ss-zero-t;
                description "Search Space With ID #0";
            }
        }
    }
    grouping sib1 {
        container cell-sel-info {
            uses cell-sel-info;
        }
        container cell-access-info {
            uses cell-access-info;
        }
        container ue-timers {
            uses ue-timers;
        }
    }
    
    
    grouping cell-l1 {
        leaf ul-central-freq {
            type uint32;
            description "UL Central Frequency";
        }
        leaf dl-central-freq {
            type uint32;
            description "DL Central Frequency";
        }
        leaf ssb-pwr {
            type uint32;
            description "SSB Power";
        }
        leaf ssb-prb-offset {
            type uint8;
            description "SSB PRB Offset";
        }
        leaf ca-lvl {
            type uint8;
            description "Cell Aggregation Level";
        }
        leaf ul-carrier-k0 { type cgdcts:scs-carrier-k0-e; }
        leaf dl-carrier-k0 { type cgdcts:scs-carrier-k0-e; }
        container prach {
            if-feature optional;
            uses prach;
        }
        container mib {
            uses mib;
        }
        container sib1 {
            uses sib1;
        }
    }
}
