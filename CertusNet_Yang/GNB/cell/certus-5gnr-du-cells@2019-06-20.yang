module certus-5gnr-du-cells {
    namespace "http://certusnet.com/5gnr/du/certus-5gnr-du-cells";
    prefix cgdcs;
    
    import certus-5gnr-du-cell-types {
        prefix cgdcts;
        revision-date 2019-06-20;
    }
    include certus-5gnr-du-cell-base {
        revision-date 2019-06-20;
    }
    include certus-5gnr-du-cell-ul-dl {
        revision-date 2019-08-23;
    }
    include certus-5gnr-du-cell-bwps {
        revision-date 2019-08-23;
    }
    include certus-5gnr-du-cell-l1 {
        revision-date 2019-06-20;
    }
    
    organization "CertusNet";
    description "This module defines du cells.";
    
    revision 2019-06-20 {
        description  "Initial revision.";
    }
    
    feature optional {
        description "The auto-generated node is std::optional type.";

    }
    
    grouping state {
        leaf admin-state {
            type cgdcts:admin-state-e;
            default BLOCKED;
            
            description "Admininstration State";
        }
        leaf oper-state {
            type cgdcts:oper-state-e;
            default UNACTIVATED;
            config false;
            
            description "Operation State";
        }
        leaf avail-state {
            type cgdcts:avail-state-e;
            default UNAVAILABLE;
            config false;
            
            description "Availability State";
        }
    }
    
    
    list du-cells {
        key "cell-id";
        
        leaf cell-id {
            type uint32;
            description "Cell ID";
        }
        uses state;

        container base {
            uses cell-base;
        }
        container ul-dl {
            uses cell-ul-dl;
        }
        container bwps {
            uses cell-bwps;
        }
        container l1 {
            uses cell-l1;
        }
        description "Cells In This DU";
    }
}
